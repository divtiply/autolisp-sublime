;; Returns CSV converted to list of lists
;; (parse-csv "1,,'2,3',4.5,'6.7',hello,'\"world\"' \",; \t" "," "\"'" nil)
(defun parse-csv (str delims quotes eols / len start end char fields records)
  (setq delims (if delims (vl-string->list delims))
        quotes (if quotes (vl-string->list quotes))
        eols   (if eols   (vl-string->list eols)))
  (setq len (strlen str)
        start 0
        end start)
  (while (< end len)
    (setq char (vl-string-elt str end))
    (cond ((member char quotes)
           (setq end (vl-string-position char str (1+ end))
                 end (if end (1+ end) len)))
          ((member char eols)
           (setq fields (cons (substr str (1+ start) (- end start)) fields)
                 records (cons (reverse fields) records)
                 fields nil
                 start (1+ end)
                 end start))
          ((member char delims)
           (setq fields (cons (substr str (1+ start) (- end start)) fields)
                 start (1+ end)
                 end start))
          (t (setq end (1+ end)))))
  (setq fields (cons (substr str (1+ start) (- len start)) fields)
        records (cons (reverse fields) records))
  (reverse records))
